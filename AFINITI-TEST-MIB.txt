AFINITI-TEST-MIB DEFINITIONS ::= BEGIN

IMPORTS
    MODULE-IDENTITY, OBJECT-TYPE, enterprises FROM SNMPv2-SMI
;

afinitiTests MODULE-IDENTITY
    LAST-UPDATED "202005140000Z"
    ORGANIZATION "Afiniti"
    CONTACT-INFO    
         "postal:   Arsalan, FSD
          email:    arsalan.dogar@yahoo.com"
    DESCRIPTION
        "MIB for afiniti test"
    REVISION     "202005140000Z"
    DESCRIPTION
        "Corrected notification example definitions"
    REVISION     "200202060000Z"
    DESCRIPTION
        "First draft"
    ::= { enterprises 53864 }

--
-- top level structure
--
versionNumber       OBJECT IDENTIFIER ::= { afinitiTests 1 }
latestSignal       OBJECT IDENTIFIER ::= { afinitiTests 2 }
diskSpace        OBJECT IDENTIFIER ::= { afinitiTests 3 }

--
-- Example scalars
--
versionNumberValue OBJECT-TYPE
    SYNTAX      OCTET STRING
    MAX-ACCESS  read-only
    STATUS      current
    DESCRIPTION
        "the value of version number string"
    DEFVAL { "6.6.1" }
    ::= { versionNumber 0 }
    
latestSignalValue OBJECT-TYPE
    SYNTAX      OCTET STRING
    MAX-ACCESS  read-only
    STATUS      current
    DESCRIPTION
        "query a Postgres table named ‘snmpSignals’ in a database named ‘afinitiTest’ and return the latest value of the column ‘signalValue’ as determined by the timestamp column ‘signalTime’"
    DEFVAL { "hello" }
    ::= { latestSignal 0 }

diskSpaceValue OBJECT-TYPE
    SYNTAX      Integer
    MAX-ACCESS  read-only
    STATUS      current
    DESCRIPTION
        "total disk space used (in bytes) for the /var/log/ folder"
    DEFVAL { 3 }
    ::= { diskSpace 0 }


-- END:  Don't forget this!
END
